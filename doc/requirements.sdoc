[DOCUMENT]
TITLE: Excalibur

[GRAMMAR]
IMPORT_FROM_FILE: grammar.sgra

[TEXT]
TITLE: Mission Statement
STATEMENT: >>>
The purpose of Excalibur is the automated checking of software sources for continuous quality
assurance.
<<<

[[SECTION]]
UID: SEC-REQUIREMENTS
TITLE: Requirements

[REQUIREMENT]
UID: REQ-1
TITLE: Running Checks on Repository State
STATEMENT: >>>
Excalibur must allow running automated checks on the repository state at a specific point in its
history.
<<<

[REQUIREMENT]
UID: REQ-2
TITLE: Running Checks on Commit Ranges
STATEMENT: >>>
Excalibur must allow running automated checks on the repository at each commit within a specified
range.
<<<

[REQUIREMENT]
UID: REQ-3
TITLE: Non-Interference with Repository State
STATEMENT: >>>
Running checks must not affect the repository state, nor leave foreign artifacts.
<<<

[REQUIREMENT]
UID: REQ-4
TITLE: Check Configuration
STATEMENT: >>>
Checks must be configurable via a configuration file that is read by Excalibur.
<<<

[REQUIREMENT]
UID: REQ-5
TITLE: Select Configuration File via Option
STATEMENT: >>>
The check configuration file must be selectable via a command line option.
<<<

[REQUIREMENT]
UID: REQ-6
TITLE: Global Check Commands
STATEMENT: >>>
It must be possible to run an external check command within the repository under test.
<<<

[REQUIREMENT]
UID: REQ-7
TITLE: Generate Check Report
STATEMENT: >>>
Excalibur must generate a report of all check results, detailing success/failure of each check as well as other relevant information such as command logs where applicable.
<<<

[REQUIREMENT]
UID: REQ-8
TITLE: Per-File Checks
STATEMENT: >>>
It must be possible to run a check command on a defined subset of files within the repository under test.
<<<

[[/SECTION]]

[[SECTION]]
UID: SEC-SPECIFICATIONS
TITLE: Specifications

[[SECTION]]
UID: SEC-SPEC-CLI-OPTIONS
TITLE: Command Line Options

[SPECIFICATION]
UID: SPEC-2
TITLE: Check Configuration File Option
STATEMENT: >>>
The check configuration file must be selectable via the command line option ``--config [FILE]`` or
``-c [FILE]``.
If the option is unset, a default value of ``./excalibur.yaml`` shall be used.

The given path shall be resolved relative to root of the repository under check.
<<<
RELATIONS:
- TYPE: Parent
  VALUE: REQ-5

[SPECIFICATION]
UID: SPEC-3
TITLE: Commit Range Option
STATEMENT: >>>
The commit range to be checked must be selectable using the ``--commit-range [RANGE]`` or the ``-r
[RANGE]`` command line option, where ``RANGE`` is a valid commit range as understood by git.
If the option is unset, a default value of ``HEAD~1..HEAD`` shall be used, checking the latest commit only.
<<<
RELATIONS:
- TYPE: Parent
  VALUE: REQ-2

[SPECIFICATION]
UID: SPEC-9
TITLE: Report Location Option
STATEMENT: >>>
The location of the generated report file shall be selectable using the ``--output [FILE]`` or the ``-o [FILE]`` command line options, where ``[FILE]`` is the desired output path.

If the option is unset, a default value of ``./report.json`` shall be used.
<<<
RELATIONS:
- TYPE: Parent
  VALUE: REQ-7

[[/SECTION]]

[SPECIFICATION]
UID: SPEC-1
TITLE: Check Configuration Format
STATEMENT: >>>
Checks must be defined in a YAML file of the following format:

.. code:: yaml

   on-repository: # A list of checks to be performed on the final repository state
   on-commit: # A list of checks to be performed on each commit in the specified range

Checks that are listed as 'on-repository' shall be run on the final commit of the specified range, or on HEAD if no range is specified.

Checks that are listed as 'on-commit' shall be run once per commit in the given range, on the respective state after that commit.

Each check listed shall be configured as follows:

.. code:: yaml

   - name: # Name of the check (required)
     command: # Command to be run
     expected-exit: # Expected exit code if the check passes
     files: # Optional: A list of files, see below
     changed-only: # True/False, see below


If the ``files`` key is not set, the check is considered a "global" check, and will be run once in the repository root.

If the ``files`` key is set to a list of file patterns, the check is considered to be "per-file", and the given command will be run for each file in the repository matching any of the given patterns. The given command will be run once for each such file.

If the ``changed-only`` field is set to ``True``, only files that have changed will be checked. For ``on-repository`` checks, a file is considered to have changed if it was modified by any commit in the given range. For ``on-commit`` checks, a file is considered to have changed if it was modified by that specific commit.

If the exit code of a check command does not match the expected value, the check shall be considered to have failed, otherwise it shall be considered to have passed.
<<<
RELATIONS:
- TYPE: Parent
  VALUE: REQ-4

[SPECIFICATION]
UID: SPEC-10
TITLE: Variables in Check Configuration
STATEMENT: >>>
A number of defined variables shall be usable within check commands, to be replaced by specific information before the check is run.

These shall include:

.. list-table:: Check Command Variables
   :widths: 3 10

   * - **Variable**
     - **Description**
   * - ``${commit-range}``
     - The commit range to be checked as given to Excalibur
   * - ``${filename}``
     - The name of the particular file being checked, if the ``files`` option is set for the check. If ``files`` is unset, it will be set to ``.``, i.e. the directory the check is run in.
<<<
RELATIONS:
- TYPE: Parent
  VALUE: SPEC-1

[SPECIFICATION]
UID: SPEC-12
TITLE: Global Check Execution
STATEMENT: >>>
For global checks (i.e. checks for which the ``files`` key is not set), the configured command shall be executed exactly once, with the working directory set to the root of the repository under check.
<<<
RELATIONS:
- TYPE: Parent
  VALUE: REQ-6

[SPECIFICATION]
UID: SPEC-6
TITLE: Commit Range Resolution
STATEMENT: >>>
A given commit range shall be resolved by running ``git rev-list [RANGE]`` within the repository under check, and parsing the output into a list of revisions.
<<<
RELATIONS:
- TYPE: Parent
  VALUE: REQ-2

[SPECIFICATION]
UID: SPEC-11
TITLE: On-Repository Check Execution
STATEMENT: >>>
On-repository checks shall be executed against the repository state at the final (most recent) commit of the specified commit range. If no commit range is specified, they shall be executed against the HEAD commit.
<<<
RELATIONS:
- TYPE: Parent
  VALUE: REQ-1

[SPECIFICATION]
UID: SPEC-14
TITLE: On-Commit Check Execution
STATEMENT: >>>
On-commit checks shall be executed once per commit in the resolved commit range (per SPEC-6), against the repository state at that commit, in order from oldest to most recent.
<<<
RELATIONS:
- TYPE: Parent
  VALUE: REQ-2

[SPECIFICATION]
UID: SPEC-8
TITLE: File Pattern Resolution
STATEMENT: >>>
For checks which include configuration via file patterns (e.g. on which files to operate), these patterns shall be resolved by standard 'glob'-rules.

Specifically:
   * ``/`` shall be the path separator denoting subdirectories
   * ``*`` shall match any number of characters (including the empty string) except path seperators
   * ``**`` shall match any number of characters, *including* path separators, but *excluding* the empty string

Other operators may also be supported.
<<<
RELATIONS:
- TYPE: Parent
  VALUE: SPEC-1

[SPECIFICATION]
UID: SPEC-13
TITLE: Per-File Check Execution
STATEMENT: >>>
For per-file checks (i.e. checks for which the ``files`` key is set), the set of target files shall first be determined by resolving the configured patterns against the repository under check per SPEC-8. The configured command shall then be executed once per matching file, with the working directory set to the root of the repository under check.
<<<
RELATIONS:
- TYPE: Parent
  VALUE: REQ-8

[SPECIFICATION]
UID: SPEC-4
TITLE: Perform Checks in Temporary Copy
STATEMENT: >>>
All IO operations on the repository under check must be performed in a temporary copy of the
repository. This copy must be deleted after use.
<<<
RELATIONS:
- TYPE: Parent
  VALUE: REQ-3

[SPECIFICATION]
UID: SPEC-7
TITLE: Check Report
STATEMENT: >>>
The final report detailing all check results shall be in JSON format. It shall have the following form:

.. code:: json

   {
     "on-repository": [
       {
         "check": <check configuration>,
         "result": "Success",
         "commit": "[commit id]"
       }
     ],
     "on-commit": [
       {
         "check": {[check definition]},
         "result": "Failure",
         "commit": "[commit id]",
         "details": {
           "expected-exit": 0,
           "actual-exit": 1,
           "logs": "[command output]"
         }
       }
     ]
   }

in which each entry contains the full check definition, and entries for failed checks contain additional information in the ``details`` field. Entries for successful checks do not contain a ``details`` field.
<<<
RELATIONS:
- TYPE: Parent
  VALUE: REQ-7

[[/SECTION]]
